TS101909202 {itu-t (0) identified-organization (4) etsi (0) ts101909 (1909) part20 (20) subpart2(2) interceptVersion (0)}

DEFINITIONS AUTOMATIC TAGS ::=

BEGIN

TARGETACTIVITYMONITOR ::= SEQUENCE
{
	version           INTEGER DEFAULT 1,   -- header, version -
  lIInstanceid         LIIDType,         -- header, who -
  timestamp          UTCTime,          -- header, when -
  targetLocation        LocationType,       -- header, where -
  direction          DirectionType,
  iRITransaction        IRITransactionType DEFAULT iRIreport,
  iRITransactionNumber     INTEGER,
  userSignal          UserSignalType,      -- Either copy or interpreted signalling
  cryptoCheckSum        BIT STRING         OPTIONAL
}

TTRAFFIC-2 ::= SEQUENCE
{
	  version          INTEGER DEFAULT 1,   -- header, version -
    lIInstanceid       LIIDType,
    iRITransactionNumber   INTEGER,
    trafficPacket       BIT STRING,
    cryptoChecksum      BIT STRING  OPTIONAL
}

CTTRAFFIC-2 ::= SEQUENCE
{
	  version          INTEGER DEFAULT 1,   -- header, version -
    lIInstanceid       LIIDType,
    correspondentCount    INTEGER,
    iRITransactionNumber   INTEGER,
    trafficPacket       BIT STRING,
    cryptoChecksum      BIT STRING  OPTIONAL
}

DirectionType ::= ENUMERATED
{
  toTarget,
  fromTarget,
  unknown
}

UserSignalType ::= CHOICE
{
  copySignal    BIT STRING,
  copyCharSignal  PrintableString,
  interpretedSignal INTEGER  -- Place holder
}

IRITransactionType ::= ENUMERATED
{
    iRIbegin,
    iRIcontinue,
    iRIend,
    iRIreport
}

LocationType ::= CHOICE
{
    geodeticData    BIT STRING,
    nameAddress     PrintableString (SIZE (1..100))
}

LIIDType ::= INTEGER (0..65535) -- 16 bit integer to identify interception

END
